(defun c:ExportBoqCSV ( / dict boq aglar net-eid pipe-eid sta-lst f fn sta-name sta-eid exd sc dbls i pts area csv-line get-dict-items calc-area _all)
(vl-load-com)
(setq fn (getfiled "Save BOQ Coordinates CSV" "Trench_Coordinates.csv" "csv" 1))
(if (not fn) (exit))
(setq f (open fn "w"))
(write-line "Station_Name,Calculated_Area_m2,X1,Z1,X2,Z2,X3,Z3,X4,Z4,X5,Z5..." f)
(defun get-dict-items (dict-ename / enlst res name val assoc3)
(setq enlst (entget dict-ename) res nil)
(while (setq assoc3 (assoc 3 enlst))
(setq name (cdr assoc3))
(setq enlst (cdr (member assoc3 enlst)))
(setq val (cdr (assoc 360 enlst)))
(setq res (append res (list (cons name val))))
)
res
)
(defun calc-area (pts / sum1 sum2 i j p1 p2)
(if (< (length pts) 3) (return 0.0))
(setq sum1 0.0 sum2 0.0 i 0 j (1- (length pts)))
(while (< i (length pts))
(setq p1 (nth i pts) p2 (nth j pts))
(setq sum1 (+ sum1 (* (car p2) (cadr p1))))
(setq sum2 (+ sum2 (* (car p1) (cadr p2))))
(setq j i)
(setq i (1+ i))
)
(abs (/ (- sum1 sum2) 2.0))
)
(defun _all (code lst / r)
(setq r '())
(foreach p lst (if (= (car p) code) (setq r (append r (list (cdr p)))))) 
r
)
(setq boq (cdr (assoc -1 (dictsearch (namedobjdict) "URBANO_BOQ"))))
(if (not boq) (progn (prompt "\nError: URBANO_BOQ not found!") (close f) (exit)))
(setq aglar (cdr (assoc -1 (dictsearch boq "AGLAR"))))
(if (not aglar) (setq aglar boq))
(setq net-eid (cdr (assoc -1 (dictsearch aglar "ASU"))))
(setq pipe-eid (cdr (assoc -1 (dictsearch net-eid "P_N2_to_N3"))))
(if (not pipe-eid) (progn (prompt "\nError: Pipe not found!") (close f) (exit)))
(setq sta-lst (get-dict-items pipe-eid))
(foreach sta sta-lst
(setq sta-name (car sta))
(setq sta-eid (cdr sta))
(if (vl-string-search "STA" sta-name)
(progn
(setq exd (cdr (assoc -1 (dictsearch sta-eid "EXCAVATION_KAZI"))))
(if exd
(progn
(setq sc (dictsearch exd "SCENARIO_LOWER"))
(if sc
(progn
(setq dbls (_all 40 sc) pts '())
(setq i 1)
(while (< i (length dbls))
(setq pts (append pts (list (list (nth i dbls) (nth (1+ i) dbls)))))
(setq i (+ i 2))
)
(setq area (calc-area pts))
(setq csv-line (strcat sta-name "," (rtos area 2 4)))
(foreach pt pts
(setq csv-line (strcat csv-line "," (rtos (car pt) 2 4) "," (rtos (cadr pt) 2 4)))
)
(write-line csv-line f)
)
)
)
)
)
)
)
(close f)
(prompt (strcat "\nData successfully exported to: " fn))
(princ)
)
